module service-function-acl {
  yang-version 1;

  namespace "urn:cisco:params:xml:ns:yang:sfc-acl";

  prefix sfc-acl;

  import ietf-access-control-list {
    prefix ietf-acl;
    revision-date 2015-03-17;
  }
  import ipfix-application-information {
    prefix ipfix-application-information;
    revision-date 2015-04-10;
  }

  organization "Cisco Systems, Inc.";
  contact "Reinaldo Penno <repenno@cisco.com>";

  revision 2015-10-01 {
    description "creating Service Function Chaining extensions to ietf-acl model";
  }

  augment "/ietf-acl:access-lists/ietf-acl:acl/ietf-acl:access-list-entries/ietf-acl:ace/ietf-acl:actions" {
    description "SFC simple filter actions";
    choice sfc-action {
    case acl-rendered-service-path {
      description "Determine the Service Function Path the packet the packet will
      traverse";
      leaf rendered-service-path {
        type string;
      }
     }
    }
  }

  augment "/ietf-acl:access-lists/ietf-acl:acl/ietf-acl:access-list-entries/ietf-acl:ace" {
    leaf sub-domain {
       type boolean;
       default false;
       description
          "H-SFC flag";
    }
  }

  augment "/ietf-acl:access-lists/ietf-acl:acl/ietf-acl:access-list-entries/ietf-acl:ace/ietf-acl:matches" {
    description "Level 7 match criteria, based on IPFIX applicationIds";
    leaf-list application-id {
      description "Application Identifier";
      type ipfix-application-information:application-id-ref;
    }
  }
}
